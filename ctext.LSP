(defun c:ctext();centraliza textos dentro de poligonos
;(load(findfile"S:/Library/Lisp-Ausenco/Biblioteca de Comandos/BIBLIOTECA_2.FAS"))
;(load(findfile"S:/Library/Lisp-Ausenco/Biblioteca de Comandos/BIBFORMULAS.FAS"))
  (command"undo""be")
  (setq p1(getpoint"\n1º ponto da janela: ")
	p2(getcorner p1"\n2º ponto da janela: ")
	txts(ssget"w" p1 p2(list(cons 0 "text")))
	<n> 0
	)
  (while(setq txt(ssname txts <n>))
    (setq txt(entget txt)
	  pt(cdr(assoc 10 txt))
	  <n>(1+ <n>)
	  )
    (command"-boundary"pt"")
    (setq bound(ssname(ssget"l")0)
	  coords(listcoordspl (list bound pt))
	  )
    (xyzlist coords)
    (setq x(/(+ x< x>)2)
	  y(/(+ y< y>)2)
	  ;txt(subst (cons 10 (list x y)) (assoc 10 txt) txt)
	  txt(subst (cons 11 (list x y)) (assoc 11 txt) txt)
	  txt(entmod txt)
	  bound(entdel bound)
	  )
    )
  (command"undo""e")
  (princ)
  )

(defun listcoordspl(pline / =p= =c= <counter> coords x y)
  (setq =p=(vlax-ename->vla-object(car pline))
	=c=(vlax-get =p= 'Coordinates)
	<counter> 0
	coords nil
	)
  (while(car =c=)
    (setq x(car =c=)
	  =c=(cdr =c=)
	  y(car =c=)
	  =c=(cdr =c=)
	  coords(vl-list*(list x y)coords)
	  )
    )
  (reverse coords)
  )

(defun xyzlist(lista / <counter>)
  (setq <counter> 0
	//x// nil
	//y// nil
	//z// nil
	)
  (while(/=(nth <counter> lista)nil)
    (setq coord(nth <counter> lista)
	  <counter>(1+ <counter>)
	  )
    (if(setq x(car coord))(setq //x//(vl-list* x //x//)))
    (if(setq y(cadr coord))(setq //y//(vl-list* y //y//)))
    (if(setq z(caddr coord))(setq //z//(vl-list* z //z//)))
    )
  (if //x//(setq x<(car(vl-sort //x// '<))x>(car(vl-sort //x// '>))))
  (if //y//(setq y<(car(vl-sort //y// '<))y>(car(vl-sort //y// '>))))
  (if //z//(setq z<(car(vl-sort //z// '<))z>(car(vl-sort //z// '>))))
  )
