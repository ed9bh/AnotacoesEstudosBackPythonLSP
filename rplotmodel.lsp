(defun c:rplotmodel()
  (vl-load-com)
  (setq base"C:\\Users\\Eric\\Box Sync\\EOLIVER CONSULT\\3033-01 - TECAR\\09 - Estudos\\EDG\\PLOTAGEM")
  (mapcar'(lambda(x)
	    (if(or(vl-string-search "-model." x)(vl-string-search "-Model." x))
	      (vl-file-rename
		(strcat base "\\" x)
		(strcat base "\\" (substr x 1(vl-string-position(ascii"-")x nil t))".pdf")
		)
	      )
	    )
	 (vl-directory-files base	 "*.pdf")
	 )
  (print)
  );(c:rplotmodel)
