;;;;;;;;;;;;;;;;;;;;;;;;;;;;;;;;;;;;;;;;;;;;;;;;;;;;;;;;;;;;;;;;Tags Inicio
(defun tags(posneg)
    ;Tags
    (if(= posneg 1)
      (setq ptLine01-A(vlax-3d-point(list(-(car ptX>Y<)4.00)(+(cadr ptX>Y<)8.00 YM)))
	    ptLine01-AA(vlax-3d-point(list(-(car ptX>Y<)4.00)(+(cadr ptX>Y<)8.00)))
	    ptLine01-B(vlax-3d-point(list(+(car ptX>Y<)82.00)(+(cadr ptX>Y<)8.00 YM)))
	    ptTxtSup(vlax-3d-point(list(+(car ptX>Y<)39.655)(+(cadr ptX>Y<)11.555 YM)))
	    ptTxtInf(vlax-3d-point(list(+(car ptX>Y<)39.655)(+(cadr ptX>Y<)4.805 YM)))
	    )
      (setq ptLine01-A(vlax-3d-point(list(+(car ptX<Y<)4.00)(+(cadr ptX>Y<)8.00 YM)))
	    ptLine01-AA(vlax-3d-point(list(+(car ptX<Y<)4.00)(+(cadr ptX>Y<)8.00)))
	    ptLine01-B(vlax-3d-point(list(-(car ptX<Y<)82.00)(+(cadr ptX>Y<)8.00 YM)))
	    ptTxtSup(vlax-3d-point(list(-(car ptX<Y<)39.655)(+(cadr ptX<Y<)11.555 YM)))
	    ptTxtInf(vlax-3d-point(list(-(car ptX<Y<)39.655)(+(cadr ptX<Y<)4.805 YM)))
	    )
      )
    ;lin01
    (vla-addline(vla-get-modelspace(vla-get-activedocument(vlax-get-acad-object)))ptLine01-A ptLine01-B)
    (setq lin01(entlast))
    (mapcar'(lambda(x)(vlax-put(vlax-ename->vla-object(entlast))(car x)(cadr x)))(list(list'Layer"FORMATO")(list'Color 6)(list'Linetype"ByLayer")))
    ;;;lin02
    (if(= YM 0)
      (progn(if lin02(if(vlax-ename->vla-object lin02)(entdel lin02)))(setq lin02 nil))
      (progn
	(vla-addline(vla-get-modelspace(vla-get-activedocument(vlax-get-acad-object)))ptLine01-AA ptLine01-A)(setq lin02(entlast))
	(mapcar'(lambda(x)(vlax-put(vlax-ename->vla-object lin02)(car x)(cadr x)))(list(list'Layer"FORMATO")(list'Color 6)(list'Linetype"ByLayer")))
	)
      )
    ;txtSup
    (setq insert(vla-addtext(vla-get-modelspace(vla-get-activedocument(vlax-get-acad-object)))txtTag ptTxtSup 4)
	  txtSup(entlast)
	  )
    (vlax-put insert 'Alignment acAlignmentMiddleCenter)(vla-put-textalignmentpoint insert ptTxtSup)(vla-put-layer insert "TX02")(vla-put-color insert 256)(vla-put-StyleName insert "ROMANS")
    ;txtInf
    (setq txtTagJCProps(strcat"JC=" (rtos jcEspessura 2 0) "mm" " - "(vl-string-translate"."","(rtos tubs 2 2))"m")
	  insert(vla-addtext(vla-get-modelspace(vla-get-activedocument(vlax-get-acad-object)))txtTagJCProps ptTxtInf 4)
	  txtInf(entlast)
	  )
    (vlax-put insert 'Alignment acAlignmentMiddleCenter)(vla-put-textalignmentpoint insert ptTxtInf)(vla-put-layer insert "TX02")(vla-put-color insert 256)(vla-put-StyleName insert "ROMANS")
    )
;;;;;;;;;;;;;;;;;;;;;;;;;;;;;;;;;;;;;;;;;;;;;;;;;;;;;;;;;;;;;;;;;Final de Insersão TAGs
;;;;;;;;;;;;;;;;;;;;;;;;;;;;;;;;;;;;;;;;;;;;;;;;;;;;;;;;;;;;;;;;;Linhas de interferencia
(defun limitline()
    (vla-addline(vla-get-modelspace(vla-get-activedocument(vlax-get-acad-object)))(vlax-3d-point ptX<Y<)(vlax-3d-point ptX<Y>))
    (mapcar'(lambda(x)(vlax-put(vlax-ename->vla-object(entlast))(car x)(cadr x)))(list(list'Layer"FORMATO")(list'Color 6)(list'Linetype"ByLayer")))
    (vla-addline(vla-get-modelspace(vla-get-activedocument(vlax-get-acad-object)))(vlax-3d-point ptX>Y<)(vlax-3d-point ptX>Y>))
    (mapcar'(lambda(x)(vlax-put(vlax-ename->vla-object(entlast))(car x)(cadr x)))(list(list'Layer"FORMATO")(list'Color 6)(list'Linetype"ByLayer")))
    )
;;;;;;;;;;;;;;;;;;;;;;;;;;;;;;;;;;;;;;;;;;;;;;;;;;;;;;;;;;;;;;;;;;;;;;;;;;;;;;;;;;;;;;;;

(defun c:jc()
  (vl-load-com)(setvar"cmdecho"0)(command"undo""be")
  (setq ptA(getpoint"\nClique no inicial ou do centro do Tubo Camisa: ")
	ptB(getpoint ptA "\tClique no ponto final ou <enter>: ")
	tubs(if ptB
	      (+(*(fix(/(abs(-(car ptA)(car ptB)))12))12)12)
	      (getint"\nDigite a extensão completa da jaqueta de concreto: ")
	      )
	txtTag(progn
		(initget 1"Hidrografia Acesso")
		(if(=(getkword"\nTipo de interferencia [Hidrografia / Acesso]: ")"Hidrografia")"FLUTUABILIDADE NEGATIVA""PROTEÇÃO MECÂNICA")
		)
	tubs(if(and(= txtTag "FLUTUABILIDADE NEGATIVA")(< tubs 24))24 tubs)
	;jcEspessura(getint"\nDigite a espessura da jaqueta de concreto ou enter para <38mm>: ")
	;jcEspessura(if jcEspessura jcEspessura 38)
	jcEspessura(if(= txtTag "PROTEÇÃO MECÂNICA")
		     38
		     (esps(vlax-get(vlax-ename->vla-object(car(entsel"\nSelecione o texto da espessura: ")))'TextString))
		     )
	)
  (if ptB
    (progn
      (setq ptX<Y<(list(-(-(car ptA)(/(-(car ptA)(car ptB))2))(/ tubs 2))(cadr ptA))
	    ptX<Y>(list(-(-(car ptA)(/(-(car ptA)(car ptB))2))(/ tubs 2))(+(cadr ptA)16))
	    ptX>Y<(list(+(-(car ptA)(/(-(car ptA)(car ptB))2))(/ tubs 2))(cadr ptA))
	    ptX>Y>(list(+(-(car ptA)(/(-(car ptA)(car ptB))2))(/ tubs 2))(+(cadr ptA)16))
	    )
      (limitline)
      )
    (progn
      (setq ptX<Y<(list(-(car ptA)(/ tubs 2))(cadr ptA))
	    ptX<Y>(list(-(car ptA)(/ tubs 2))(+(cadr ptA)16))
	    ptX>Y<(list(+(car ptA)(/ tubs 2))(cadr ptA))
	    ptX>Y>(list(+(car ptA)(/ tubs 2))(+(cadr ptA)16))
	    )
      (limitline)
      )
    )
  (setq lin01 nil lin02 nil txtSup nil txtInf nil YM 0)
  (while(= 5(car(setq mouse(grread 't 13 0))))
    (command"redraw")
    (if(= lin01 nil)(princ)(mapcar'(lambda(x)(if x(entdel x)))(list lin01 lin02 txtSup txtInf)))
    (setq mouse(cadr mouse))
    (cond
      ;;;Inicio Posição mesma Linha
      ((and(>(car mouse)(-(car ptX<Y<)(/(-(car ptX<Y<)(car ptX>Y<))2)))(>(cadr mouse)(cadr ptX<Y<))(<(cadr mouse)(+(cadr ptX<Y<)16)))
       (progn(setq YM 0)(tags 1)))
      ((and(<(car mouse)(-(car ptX<Y<)(/(-(car ptX<Y<)(car ptX>Y<))2)))(>(cadr mouse)(cadr ptX<Y<))(<(cadr mouse)(+(cadr ptX<Y<)16)))
       (progn(setq YM 0)(tags 0)))
      ;;;Final Posição mesma Linha
      ;;;Inicio Posição Superior
      ((and(>(car mouse)(-(car ptX<Y<)(/(-(car ptX<Y<)(car ptX>Y<))2)))(>(cadr mouse)(+(cadr ptX<Y<)16)))
       (progn(setq YM 16)(tags 1)))
      ((and(<(car mouse)(-(car ptX<Y<)(/(-(car ptX<Y<)(car ptX>Y<))2)))(>(cadr mouse)(+(cadr ptX<Y<)16)))
       (progn(setq YM 16)(tags 0)))
      ;;;Final Posição Superior
      ;;;Inicio Posição Inferior
      ((and(>(car mouse)(-(car ptX<Y<)(/(-(car ptX<Y<)(car ptX>Y<))2)))(<(cadr mouse)(cadr ptX<Y<)))
       (progn(setq YM -16)(tags 1)))
      ((and(<(car mouse)(-(car ptX<Y<)(/(-(car ptX<Y<)(car ptX>Y<))2)))(<(cadr mouse)(cadr ptX<Y<)))
       (progn(setq YM -16)(tags 0)))
      ;;;Final Posição Inferior
      )
    )
  (command"undo""e")(setvar"cmdecho"0)(princ)
  )

(defun esps(dutesp)
  (cond
    ((= dutesp"0,344")114)
    ((= dutesp"0,375")110)
    ((= dutesp"0,406")106)
    ((= dutesp"0,438")100)
    ((= dutesp"0,469")96)
    ((= dutesp"0,500")92)
    ((= dutesp"0,531")86)
    ((= dutesp"0,562")82)
    ((= dutesp"0,594")76)
    ((= dutesp"0,625")72)
    ((= dutesp"0,656")68)
    ((= dutesp"0,657")68);***
    ((= dutesp"0,688")62)
    ((= dutesp"0,719")58)
    ((= dutesp"0,750")52)
    ((= dutesp"0,781")46)
    ((= dutesp"0,812")42)
    ((= dutesp"0,844")38)
    ((= dutesp"0,875")38)
    ((= dutesp"0,907")38)
    ((= dutesp"0,938")38)
    ((= dutesp"1,000")38)
    ((= dutesp"1,062")38)
    ((= dutesp"1,125")38)
    )
  )
