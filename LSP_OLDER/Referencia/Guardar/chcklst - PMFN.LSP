(defun c:pmfn()(setvar"cmdecho"0)
  (vl-load-com)(setvar"dimzin"0)
  (command"layout""set"(car(layoutlist)))
  (vla-zoomwindow
    (vlax-get-acad-object)
    (vlax-3D-point(list 948.430 465.387))(vlax-3D-point(list 1054.432 486.908))
    )
  ;;;Texto Errado
  (if(setq txterrado(ssget"x"'((0 . "text,mtext")(1 . "FLUTUAÇÃO NEGATIVA"))))
    (mapcar'(lambda(x)(vlax-put(vlax-ename->vla-object(cadr x))'TextString"FLUTUABILIDADE NEGATIVA"))(ssnamex txterrado))
    )
  ;;;
  (setq jc(ssget"x"'((0 . "text")(410 . "model")(1 . "JC***************")))
	jc(mapcar'(lambda(x)(cadr x))(ssnamex jc))
	;
	ProtecaoMecanica(ssget"x"'((0 . "text")(410 . "model")(1 . "PROTEÇÃO MECÂNICA")))
	ProtecaoMecanica(if ProtecaoMecanica(mapcar'(lambda(x)(cadr x))(ssnamex ProtecaoMecanica)))
	;
	FlutuabilidadeNegativa(ssget"x"'((0 . "text")(410 . "model")(1 . "FLUTUABILIDADE NEGATIVA")))
	FlutuabilidadeNegativa(if FlutuabilidadeNegativa(mapcar'(lambda(x)(cadr x))(ssnamex FlutuabilidadeNegativa)))
	;
	FnTotalLista nil
	)
  ;;;
  (setq n -1 cP -1 cF -1 pmLst nil fnLst nil pmTotal nil fnTotal nil)
  (if ProtecaoMecanica
    (while(setq pmObj(nth(setq cP(1+ cP))ProtecaoMecanica))(setq pmLst(vl-list*(list(vlax-get(vlax-ename->vla-object pmObj)'TextAlignmentPoint)pmObj)pmLst)))
    )
  (if FlutuabilidadeNegativa
    (while(setq fnObj(nth(setq cF(1+ cF))FlutuabilidadeNegativa))(setq fnLst(vl-list*(list(vlax-get(vlax-ename->vla-object fnObj)'TextAlignmentPoint)fnObj)fnLst)))
    )
  ;;;
  (repeat(length jc)
    (setq jcObj(nth(setq n(1+ n))jc)
	  jcObj(list(vlax-get(vlax-ename->vla-object jcObj)'TextAlignmentPoint)jcObj)
	  )
    (if pmLst
      (setq nearPMlst(mapcar'(lambda(x)(list(abs(-(car(car jcObj))(car(car x))))(cadr x)))pmLst)
	    nearPMlst(vl-sort nearPMlst '(lambda(e1 e2)(<(car e1)(car e2))))
	    )
      )
    (if fnLst
      (setq nearFMlst(mapcar'(lambda(x)(list(abs(-(car(car jcObj))(car(car x))))(cadr x)))fnLst)
	    nearFMlst(vl-sort nearFMlst '(lambda(e1 e2)(<(car e1)(car e2))))
	    )
      )
    (if(and ProtecaoMecanica FlutuabilidadeNegativa)
      (if(<(car(car nearPMlst))(car(car nearFMlst)))
	(setq pmTotal
	       (vl-list*(read(vl-string-translate",""."(vl-string-right-trim"m"(substr(vlax-get(vlax-ename->vla-object(cadr jcObj))'TextString)11))))
			pmTotal))
	(setq fnTotal
	       (vl-list*(read(vl-string-translate",""."(vl-string-right-trim"m"(substr(vlax-get(vlax-ename->vla-object(cadr jcObj))'TextString)11))))
			fnTotal)
	      FnTotalLista(vl-list*(vlax-get(vlax-ename->vla-object(cadr jcObj))'TextString)FnTotalLista)
	      )
	)
      (if ProtecaoMecanica
	(setq pmTotal
	       (vl-list*(read(vl-string-translate",""."(vl-string-right-trim"m"(substr(vlax-get(vlax-ename->vla-object(cadr jcObj))'TextString)11))))
			pmTotal))
	(setq fnTotal
	       (vl-list*(read(vl-string-translate",""."(vl-string-right-trim"m"(substr(vlax-get(vlax-ename->vla-object(cadr jcObj))'TextString)11))))
			fnTotal)
	      FnTotalLista(vl-list*(vlax-get(vlax-ename->vla-object(cadr jcObj))'TextString)FnTotalLista)
	      )
	)
      )
    )
  ;;;
  (if ProtecaoMecanica
    (vlax-put(vlax-ename->vla-object(ssname(ssget"w"'(1023.272 476.787)'(1037.048 480.381)'((0 . "text")))0))'Textstring(vl-string-translate"."","(rtos(apply '+ pmTotal)2 2)))
    (vlax-put(vlax-ename->vla-object(ssname(ssget"w"'(1023.272 476.787)'(1037.048 480.381)'((0 . "text")))0))'Textstring"-")
    )
  (if FlutuabilidadeNegativa
    (vlax-put(vlax-ename->vla-object(ssname(ssget"w"'(1017.392 471.587)'(1040.629 475.788)'((0 . "text")))0))'Textstring(vl-string-translate"."","(rtos(apply '+ fnTotal)2 2)))
    (vlax-put(vlax-ename->vla-object(ssname(ssget"w"'(1017.392 471.587)'(1040.629 475.788)'((0 . "text")))0))'Textstring"-")
    )
  (princ(strcat"\n"(rtos(+(length pmTotal)(length fntotal))2 0)" Jaquetas de Concreto"
	       (if ProtecaoMecanica(strcat"\nProteção Mecânica - Quant.: "(rtos(length pmTotal)2 0)" Ext.: "(rtos(apply '+ pmTotal)2))"\nSem Proteção Mecânica...")
	       (if FlutuabilidadeNegativa"\nTabela Flutuabilidade Negativa""\nSem Flutuablidade Negativa...")
	       )
	)
  (setq t114 0 t110 0 t106 0 t100 0 t96 0 t92 0 t86 0 t82 0 t76 0 t72 0 t68 0 t62 0 t58 0 t52 0 t46 0 t42 0 t38 0)
  (setq c114 0 c110 0 c106 0 c100 0 c96 0 c92 0 c86 0 c82 0 c76 0 c72 0 c68 0 c62 0 c58 0 c52 0 c46 0 c42 0 c38 0)
  (setq n -1)
  (repeat(length FnTotalLista)
    (setq z(nth(setq n(1+ n))FnTotalLista)
	  esp(substr z(+(vl-string-search"="z)2))
	  esp(substr esp 1(-(vl-string-search"m"z)3))
	  comp(substr z(+(vl-string-search"-"z)3))
	  comp(read(vl-string-translate",""."(vl-string-right-trim"m"comp)))
	  )
    (cond
      ((= esp"114")(setq t114(1+ t114)c114(+ comp c114)))
      ((= esp"110")(setq t110(1+ t110)c110(+ comp c110)))
      ((= esp"106")(setq t106(1+ t106)c106(+ comp c106)))
      ((= esp"100")(setq t100(1+ t100)c100(+ comp c100)))
      ((= esp"96")(setq t96(1+ t96)c96(+ comp c96)))
      ((= esp"92")(setq t92(1+ t92)c92(+ comp c92)))
      ((= esp"86")(setq t86(1+ t86)c86(+ comp c86)))
      ((= esp"82")(setq t82(1+ t82)c82(+ comp c82)))
      ((= esp"76")(setq t76(1+ t76)c76(+ comp c76)))
      ((= esp"72")(setq t72(1+ t72)c72(+ comp c72)))
      ((= esp"68")(setq t68(1+ t68)c68(+ comp c68)))
      ((= esp"62")(setq t62(1+ t62)c62(+ comp c62)))
      ((= esp"58")(setq t58(1+ t58)c58(+ comp c58)))
      ((= esp"52")(setq t52(1+ t52)c52(+ comp c52)))
      ((= esp"46")(setq t46(1+ t46)c46(+ comp c46)))
      ((= esp"42")(setq t42(1+ t42)c42(+ comp c42)))
      ((= esp"38")(setq t38(1+ t38)c38(+ comp c38)))
      )
    )
  (mapcar'(lambda(x)(if(/=(cadr x)0)
		      (princ
			(strcat"\n------------------------------\n"
			       "Esp.: "(car x)" - Quant.: "(rtos(cadr x)2 0)" Extensão: "(rtos(caddr x)2))
			)
		      )
	    )
	 (list
	   (list "114" t114 c114)
	   (list "110" t110 c110)
	   (list "106" t106 c106)
	   (list "100" t100 c100)
	   (list "96" t96 c96)
	   (list "92" t92 c92)
	   (list "86" t86 c86)
	   (list "82" t82 c82)
	   (list "76" t76 c76)
	   (list "72" t72 c72)
	   (list "68" t68 c68)
	   (list "62" t62 c62)
	   (list "58" t58 c58)
	   (list "52" t52 c52)
	   (list "46" t46 c46)
	   (list "42" t42 c42)
	   (list "38" t38 c38)
	   )
	 )
  (setvar"cmdecho"1)(princ)
  (princ)
  )
