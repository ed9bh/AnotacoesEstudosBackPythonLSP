;(vlisp-compile 'st "C:\\Users\\ericd\\OneDrive\\2 - Work\\1 - TOOLBOX\\Programas\\C3D\\FitSampleLine.LSP" "C:\\Users\\ericd\\OneDrive\\2 - Work\\1 - TOOLBOX\\Programas\\C3D\\FitSampleLineCivil3D_FreeVersion")
;(vlisp-compile 'st "C:\\Users\\GOMEE11\\Documents\\_LISP\\EDG_Lisps\\C3D\\FitSampleLine.LSP" "C:\\Users\\GOMEE11\\Documents\\_LISP\\EDG_Lisps\\C3D\\FitSampleLineCivil3D_FreeVersion")

(defun c:fitSampleLine()
  (vl-load-com)
  (setvar'cmdecho 0)
  (setq
    err *error*
    )
  (defun *error*(msg)
    (setq *error* err)
    (princ "Comando cancelado ou ocorreu um erro!!!")
    (setq
      Ajuda(progn
	     (initget 11 "Ajuda Continuar")
	     (getkword "\nPrecisa de [Ajuda / Continuar] ? : ")
	     )
      Ajuda(if (= Ajuda "Ajuda")
	     (progn
	       (setq
		 iex(vlax-get-or-create-object "InternetExplorer.Application")
		 )
	       (vla-put-visible iex :vlax-true)
	       (vlax-invoke-method iex 'Navigate2 "https://youtu.be/lojuowcMsuA")
	       )
	     )
      )
    (setvar'cmdecho 1)
    (princ)
   )
  
  (setq
    eEnty(entsel"\nSelecione uma Sample Line, Polyline, Line ou Arco : ")
    eType(cdr(assoc 0(entget (car eEnty))))
    vEnty(vlax-ename->vla-object(car eEnty))
    model(vla-get-modelspace(vla-get-activedocument(vlax-get-acad-object)))
    )

  (if(= eType "AECC_SAMPLE_LINE")
    (progn
      (command"undo""be")
      (setq
	p1 (vlax-get (vlax-invoke (vlax-get vEnty 'Vertices) 'Item 0) 'Location)
	p2 (vlax-get (vlax-invoke (vlax-get vEnty 'Vertices) 'Item 1) 'Location)
	ang (angle p1 p2)
	dist (distance p1 p2)
	pMid (polar p1 ang (/ dist 2))
	point(getpoint pMid "\tPonto da direção a extender : ")
	d1 (distance p1 point)
	d2 (distance point p2)
	d1X (distance pMid point)
	d2X (distance point pMid)
	)
      (if (< d1 d2)
	(progn
	  (setq
	    pEx (polar pMid ang (*(abs d1X)-1))
	    )
	  (vlax-put (vlax-invoke (vlax-get vEnty 'Vertices) 'Item 0) 'Location pEx)
	  )
	(progn
	  (setq
	    pEx (polar pMid ang (abs d2X))
	    )
	  (vlax-put (vlax-invoke (vlax-get vEnty 'Vertices) 'Item 1) 'Location pEx)
	  )
	)
      (command"undo""e")
      )
    )

  (if(or(= eType "LINE")(= eType "LWPOLYLINE")(= eType "ARC"))
    (while (setq selPoint1(getpoint"\nPonto 1 : "))
      (setq selPoint2(getpoint selPoint1 "\tPonto 2 : ")
	    ssSample(ssget"f"(list selPoint1 selPoint2)'((0 . "AECC_SAMPLE_LINE")))
	    )
      (foreach x (ssnamex ssSample)
	;(print (cadr x))
	(setq vX(vlax-ename->vla-object (cadr x) )
	      )
	(defun *error*(msg)
	  (setq *error* err)
	  (princ "Comando cancelado ou ocorreu um erro!!!")
	  (if xl
	    (vla-delete xl)
	    )
	  (command-s"undo""e")
	  (setq
	    Ajuda(progn
		   (initget 11 "Ajuda Continuar")
		   (getkword "\nPrecisa de [Ajuda / Continuar] ? : ")
		   )
	    Ajuda(if (= Ajuda "Ajuda")
		   (progn
		     (setq
		       iex(vlax-get-or-create-object "InternetExplorer.Application")
		       )
		     (vla-put-visible iex :vlax-true)
		     (vlax-invoke-method iex 'Navigate2 "https://youtu.be/lojuowcMsuA")
		     )
		   )
	    )
	  (setvar'cmdecho 1)
	  (princ)
	  )
	(setq
	      p1 (vlax-get (vlax-invoke (vlax-get vX 'Vertices) 'Item 0) 'Location)
	      p2 (vlax-get (vlax-invoke (vlax-get vX 'Vertices) 'Item 1) 'Location)
	      p1 (list (car p1) (cadr p1) 0)
	      p2 (list (car p2) (cadr p2) 0)
	      xl (vla-addxline model (vlax-3d-point p1) (vlax-3d-point p2))
	      ang (angle p1 p2)
	      dist (distance p1 p2)
	      pMid(vlax-invoke vX 'IntersectWith (vlax-get(vlax-get vX 'Parent)'Parent) acExtendNone)
	      point(vlax-invoke xl 'IntersectWith vEnty acExtendNone)
	      point(list (nth 0 point) (nth 1 point) 0)
	      d1 (distance p1 point)
	      d2 (distance point p2)
	      dX (distance pMid point)
	      )
	(vla-put-visible xl :vlax-false)
	(if (equal (angle pMid point) (angle pMid p1) 0.001)
	  (progn
	    (setq
	      pEx (polar pMid ang (*(abs dX)-1))
	      )
	    (vlax-put (vlax-invoke (vlax-get vX 'Vertices) 'Item 0) 'Location pEx)
	    )
	  )
	(if (equal (angle pMid point) (angle pMid p2) 0.001)
	  (progn
	    (setq
	      pEx (polar pMid ang (abs dX))
	      )
	    (vlax-put (vlax-invoke (vlax-get vX 'Vertices) 'Item 1) 'Location pEx)
	    )
	  )
	(vla-delete xl)
	(command"undo""e")
	)
      )
    )
  (setq *error* err)
  (setvar'cmdecho 1)
  (princ)
  )

(princ"\n\t ||| Comando ===> FitSampleLine")
(princ)
