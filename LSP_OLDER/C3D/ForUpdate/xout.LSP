(defun c:xout()
  (vl-load-com)
  ;(vlax-put (vlax-ename->vla-object(car(entsel))) 'Visible 0)
  ;styleName (RO) = "_EPC_CDN_NATURAL"
  ;(vlax-dump-object(vlax-ename->vla-object(car(entsel)))t)
  ;(entget(car(entsel)))
  ;(0 . "AECC_TIN_SURFACE")
  (setvar'cmdecho 0)
  (setq surfaces
	 (ssget"x"'((0 . "AECC_TIN_SURFACE")))
	surfList nil
	)
  (foreach s (ssnamex surfaces)
    (progn
      (setq vs(vlax-ename->vla-object (cadr s))
	    sty(vlax-get vs 'StyleName)
	    )
      (if(= sty "_EPC_CDN_NATURAL")
	(setq surfList(vl-list* vs surfList))
	)
      )
    )
  (setq name(getvar'dwgname)
	folder(getvar'dwgprefix)
	name(vl-string-subst "_ACAD" "_AC3D" name)
	)
  (vl-file-delete (strcat folder name))
  (mapcar'(lambda(x)(vlax-put x 'Visible 0)) surfList )
  (redraw)
  (setvar'filedia 0)
  (command"AECEXPORTTOAUTOCAD2010"(strcat folder name))
  (setvar'filedia 1)
  (mapcar'(lambda(x)(vlax-put x 'Visible -1)) surfList )
  (redraw)
  (setvar'cmdecho 1)
  (princ)
  )
