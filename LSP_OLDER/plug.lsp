(defun c:plug()
  (vl-load-com)
  (setvar'cmdecho 0)
  (setq model(vla-get-modelspace(vla-get-activedocument(vlax-get-acad-object))))
  (vla-getentity(vla-get-utility(vla-get-activedocument(vlax-get-acad-object)))'plug1 'pt "\nSelecione a primeira polylinha a plugar: ")
  (vla-getentity(vla-get-utility(vla-get-activedocument(vlax-get-acad-object)))'plug2 'pt "\tSelecione a segunda polylinha a plugar: ")
  ;(vlax-dump-object plug1)	(vlax-dump-object plug2)
  (if(/=(vla-get-ObjectName plug1)"AcDbPolyline")
    (if(=(vla-get-ObjectName plug1)"AcDbLine")
      (progn
	(initget 1 "Sim Nao")
	(if(=(getkword"\nEsta entidade não é uma polylinha, deseja convertela para polylinha? [Sim/Nao]: ")"Sim")
	  (progn(command"pedit"(vlax-vla-object->ename plug1)"")(setq plug1(vlax-ename->vla-object(entlast)))))))
    )
  (if(/=(vla-get-ObjectName plug2)"AcDbPolyline")
    (if(=(vla-get-ObjectName plug2)"AcDbLine")
      (progn
	(initget 1 "Sim Nao")
	(if(=(getkword"\nEsta entidade não é uma polylinha, deseja convertela para polylinha? [Sim/Nao]: ")"Sim")
	  (progn(command"pedit"(vlax-vla-object->ename plug2)"")(setq plug2(vlax-ename->vla-object(entlast)))))))
    )
  (if(and(=(vla-get-ObjectName plug1)"AcDbPolyline")(=(vla-get-ObjectName plug2)"AcDbPolyline"))
    (progn
      (setq
	p1SP(vlax-curve-getstartpoint plug1)
	p1EP(vlax-curve-getendpoint plug1)
	p2SP(vlax-curve-getstartpoint plug2)
	p2EP(vlax-curve-getendpoint plug2)
	d12SS(list(distance p1SP p2SP)p1SP p2SP)
	d12SE(list(distance p1SP p2EP)p1SP p2EP)
	d12ES(list(distance p1EP p2SP)p1EP p2SP)
	d12EE(list(distance p1EP p2EP)p1EP p2EP)
	PointList(list d12SS d12SE d12ES d12EE)
	PointList(vl-sort PointList '(lambda(a b)(<(car a)(car b))))
	plug(vla-addline model (vlax-3d-point(cadr(car PointList)))(vlax-3d-point(caddr(car PointList))))
	)
      (command"pedit"(vlax-vla-object->ename plug1)"join"(vlax-vla-object->ename plug)(vlax-vla-object->ename plug2)"""")
      )
    )
  (setvar'cmdecho 1)
  (princ)
  )
