(defun c:explodeatt (/ *error* main doc)
    (vl-load-com)
    (defun main ()
        (vla-StartUndoMark (setq doc (vla-get-ActiveDocument (vlax-get-acad-object))))

        (setq ss(sssetfirst nil (ssget '((0 . "ATTDEF")))))

        (foreach x (ssnamex (cadr ss))
            (if (>(car x)0)
                (progn
                    (setq
                        v (vlax-ename->vla-object (cadr x))
                        p (vlax-get v 'InsertionPoint)
                        r (vlax-get v 'Rotation)
                        h (vlax-get v 'Height)
                        s (vlax-get v 'StyleName)
                        c (vlax-get v 'TrueColor)
                        a (vlax-get v 'Alignment)
                        l (vlax-get v 'Layer)
                        TAGSTRING (vlax-get v 'TagString)
                        model(vla-get-ModelSpace doc)
                    )
                    (setq
                        txt (vla-AddText model TAGSTRING (vlax-3d-point p) h)
                    )

                    (vlax-put txt 'Rotation r)
                    (vlax-put txt 'StyleName s)
                    (vlax-put txt 'Layer l)
                    ;(vla-put-TrueColor txt 'TrueColor c)
                    (vla-put-Alignment txt a)
                )
            )
        )
        
        (vla-EndUndoMark doc)
        (princ)
    )
    (defun *error*(s)
        (princ s)
        (vla-EndUndoMark doc)
        (princ)
    )
    (main)
)
